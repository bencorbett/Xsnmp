XSNMP-MIB DEFINITIONS ::= BEGIN

IMPORTS
    MODULE-IDENTITY, OBJECT-TYPE,
        enterprises, Integer32, Counter32, Counter64, Gauge32
        FROM SNMPv2-SMI
        DisplayString 
        FROM SNMPv2-TC;         

lcorp MODULE-IDENTITY

    LAST-UPDATED "201101040000Z"

    ORGANIZATION "LithiumCorp Pty Ltd"
    CONTACT-INFO "LithiumCorp Support
          Postal: 9/55 Auburn St
                  SUTHERLAND NSW 2232
                  Australia
             Tel: +61 2 8517 1001
          E-mail: support@lithiumcorp.com"
    DESCRIPTION "Xsnmp MIB"

    REVISION "201101040000Z"
        DESCRIPTION "Added failed enumerator to battery status, removed LocalMDC from Xsan Volume"
::= { enterprises 20038 }

-- Structure
--
-- xsnmp
-- |-> xsnmpObjects
--     |-> xsan (1)
--     |-> xserve (2)
--     |-> ram (3)
--     |-> fs (4)
--     |-> xsnmpInternal (5)
--     |-> raid (6)
--     |-> timeMachine (7)

xsnmp                OBJECT IDENTIFIER ::= { lcorp 2 }
xsnmpObjects         OBJECT IDENTIFIER ::= { xsnmp 1 }
   
-- Xsan Group

xsan OBJECT IDENTIFIER ::= { xsnmpObjects 1 }
   
-- Xsan Information (static table)
    
-- Xsan Volumes

xsanVolumeTable OBJECT-TYPE
    SYNTAX SEQUENCE OF XsanVolumeEntry
    MAX-ACCESS not-accessible
    STATUS  current
    DESCRIPTION
    "Volumes (FSS) reported by cvadmin"
::= { xsan 1 }

xsanVolumeEntry OBJECT-TYPE
    SYNTAX     XsanVolumeEntry
    MAX-ACCESS not-accessible
    STATUS     current
    DESCRIPTION
        "An entry per unique Volume (FSS) reported by cvadmin"
    INDEX      { xsanVolumeIndex }
::= { xsanVolumeTable 1 }

XsanVolumeEntry ::= SEQUENCE {
    xsanVolumeIndex                 Integer32,
    xsanVolumeName                  DisplayString,
    xsanVolumeFSSIndex              Integer32,
    xsanVolumeState                 INTEGER,
    xsanVolumeStateMessage          DisplayString,
    xsanVolumeLastAdminAction       DisplayString,
    xsanVolumeLastTermination       DisplayString,
    xsanVolumeLaunchCount           Counter32,
    xsanVolumeCoreDumpCount         Counter32,
    xsanVolumeFlags                 DisplayString,
    xsanVolumeCreated               DisplayString,
    xsanVolumeActiveConnections     Gauge32,
    xsanVolumeFsBlockSize           Gauge32,
    xsanVolumeMsgBufferSize         Gauge32,
    xsanVolumeDiskDevices           Gauge32,
    xsanVolumeStripeGroups          Gauge32,
    xsanVolumeTotalKBlocks          Gauge32,
    xsanVolumeFreeKBlocks           Gauge32,
    xsanVolumeTotalBlocks           Counter64,
    xsanVolumeFreeBlocks            Counter64,
    xsanVolumeUtilization           Gauge32,
    xsanVolumePid                   Gauge32,
    xsanVolumePort                  Gauge32,
    xsanVolumeTotalMBytes           Gauge32,
    xsanVolumeFreeMBytes            Gauge32,
    xsanVolumeUsedMBytes            Gauge32,
    xsanVolumeControllerAddress     DisplayString,
    xsanVolumeControllerIndex       INTEGER
}

xsanVolumeIndex OBJECT-TYPE
    SYNTAX  Integer32 (1..65535)
    MAX-ACCESS  not-accessible
    STATUS  current
    DESCRIPTION
    "Volume index assigned by Xsnmp."
::= { xsanVolumeEntry 1 }

xsanVolumeName OBJECT-TYPE
    SYNTAX  DisplayString
    MAX-ACCESS  read-only
    STATUS  current
    DESCRIPTION
    "The name of the FSS as reported in fsmlist"
::= { xsanVolumeEntry 2 }

xsanVolumeFSSIndex OBJECT-TYPE
    SYNTAX  Integer32
    MAX-ACCESS  read-only
    STATUS  current
    DESCRIPTION
    "The index of the FSS as reported in fsmlist"
::= { xsanVolumeEntry 3 }

xsanVolumeState OBJECT-TYPE
    SYNTAX INTEGER {
        registered (1), 
        stopped (2),
        unknown (0)
    }
    MAX-ACCESS  read-only
    STATUS  current
    DESCRIPTION
    "The state of the FSS as reported in fsmlist"
::= { xsanVolumeEntry 4 }

xsanVolumeStateMessage OBJECT-TYPE
    SYNTAX  DisplayString
    MAX-ACCESS  read-only
    STATUS  current
    DESCRIPTION
    "The state messge for the FSS as reported in fsmlist"
::= { xsanVolumeEntry 5 }

xsanVolumeLastAdminAction OBJECT-TYPE
    SYNTAX  DisplayString
    MAX-ACCESS  read-only
    STATUS  current
    DESCRIPTION
    "The last admin action message for the FSS as reported in fsmlist"
::= { xsanVolumeEntry 6 }

xsanVolumeLastTermination OBJECT-TYPE
    SYNTAX  DisplayString
    MAX-ACCESS  read-only
    STATUS  current
    DESCRIPTION
    "The last termination message for the FSS as reported in fsmlist"
::= { xsanVolumeEntry 7 }

xsanVolumeLaunchCount OBJECT-TYPE
    SYNTAX  Counter32
    MAX-ACCESS  read-only
    STATUS  current
    DESCRIPTION
    "The number of launches for the FSS as reported in fsmlist"
::= { xsanVolumeEntry 8 }

xsanVolumeCoreDumpCount OBJECT-TYPE
    SYNTAX  Counter32
    MAX-ACCESS  read-only
    STATUS  current
    DESCRIPTION
    "The number of crashes and core dumps for the FSS as reported in fsmlist"
::= { xsanVolumeEntry 9 }

xsanVolumeFlags OBJECT-TYPE
    SYNTAX  DisplayString
    MAX-ACCESS  read-only
    STATUS  current
    DESCRIPTION
    "The operating flags for the FSS as reported in fsmlist"
::= { xsanVolumeEntry 10 }

xsanVolumeCreated OBJECT-TYPE
    SYNTAX  DisplayString
    MAX-ACCESS  read-only
    STATUS  current
    DESCRIPTION
    "Date the Volume was created (e.g. Tue Jun  9 17:34:52 2009)"
::= { xsanVolumeEntry 11 }

xsanVolumeActiveConnections OBJECT-TYPE
    SYNTAX  Gauge32
    UNITS   "connections"
    MAX-ACCESS  read-only
    STATUS  current
    DESCRIPTION
    "Number of active connections"
::= { xsanVolumeEntry 12 }

xsanVolumeFsBlockSize OBJECT-TYPE
    SYNTAX  Gauge32
    UNITS   "KBytes"
    MAX-ACCESS  read-only
    STATUS  current
    DESCRIPTION
    "File system block size in KBytes"
::= { xsanVolumeEntry 13 }

xsanVolumeMsgBufferSize OBJECT-TYPE
    SYNTAX  Gauge32
    MAX-ACCESS  read-only
    STATUS  current
    DESCRIPTION
    "Message buffer size"
::= { xsanVolumeEntry 14 }

xsanVolumeDiskDevices OBJECT-TYPE
    SYNTAX  Gauge32
    MAX-ACCESS  read-only
    STATUS  current
    DESCRIPTION
    "Number of disk devices used by the volume"
::= { xsanVolumeEntry 15 }

xsanVolumeStripeGroups OBJECT-TYPE
    SYNTAX  Gauge32
    MAX-ACCESS  read-only
    STATUS  current
    DESCRIPTION
    "Number of stripe groups configured for the volume"
::= { xsanVolumeEntry 16 }

xsanVolumeTotalKBlocks OBJECT-TYPE
    SYNTAX  Gauge32
    UNITS   "KBlocks"
    MAX-ACCESS  read-only
    STATUS  current
    DESCRIPTION
    "Total number of blocks divided by 1,000 (KiloBlocks)"
::= { xsanVolumeEntry 17 }

xsanVolumeFreeKBlocks OBJECT-TYPE
    SYNTAX  Gauge32
    UNITS   "KBlocks"
    MAX-ACCESS  read-only
    STATUS  current
    DESCRIPTION
    "Number of free blocks divided by 1,000 (KiloBlocks)"
::= { xsanVolumeEntry 18 }

xsanVolumeTotalBlocks OBJECT-TYPE
    SYNTAX  Counter64
    UNITS   "Blocks"
    MAX-ACCESS  read-only
    STATUS  current
    DESCRIPTION
    "Total number of blocks"
::= { xsanVolumeEntry 19 }

xsanVolumeFreeBlocks OBJECT-TYPE
    SYNTAX  Counter64
    UNITS   "Blocks"
    MAX-ACCESS  read-only
    STATUS  current
    DESCRIPTION
    "Number of free blocks"
::= { xsanVolumeEntry 20 }

xsanVolumeUtilization OBJECT-TYPE
    SYNTAX  Gauge32
    UNITS   "%"
    MAX-ACCESS  read-only
    STATUS  current
    DESCRIPTION
    "The Utilization of the drive expressed as free space over total size."
::= { xsanVolumeEntry 21 }

xsanVolumePid OBJECT-TYPE
    SYNTAX  Gauge32
    MAX-ACCESS  read-only
    STATUS  current
    DESCRIPTION
    "The process ID of the FSS as reported by fsmlist."
::= { xsanVolumeEntry 22 }

xsanVolumePort OBJECT-TYPE
    SYNTAX  Gauge32
    MAX-ACCESS  read-only
    STATUS  current
    DESCRIPTION
    "The port of the FSS as reported by fsmlist."
::= { xsanVolumeEntry 23 }

xsanVolumeTotalMBytes OBJECT-TYPE
    SYNTAX  Gauge32
    UNITS   "MBytes"
    MAX-ACCESS  read-only
    STATUS  current
    DESCRIPTION
    "Total number of bytes divided by 1024 * 1024 (Megabytes)"
::= { xsanVolumeEntry 24 }

xsanVolumeFreeMBytes OBJECT-TYPE
    SYNTAX  Gauge32
    UNITS   "MBytes"
    MAX-ACCESS  read-only
    STATUS  current
    DESCRIPTION
    "The number of free bytes divided by 1024 * 1024 (Megabytes)"
::= { xsanVolumeEntry 25 }

xsanVolumeUsedMBytes OBJECT-TYPE
    SYNTAX  Gauge32
    UNITS   "MBytes"
    MAX-ACCESS  read-only
    STATUS  current
    DESCRIPTION
    "The number of used bytes divided by 1024 * 1024 (Megabytes)"
::= { xsanVolumeEntry 26 }

xsanVolumeControllerAddress OBJECT-TYPE
    SYNTAX  DisplayString
    MAX-ACCESS  read-only
    STATUS  current
    DESCRIPTION
    "The IP Address of the metadata controller"
::= { xsanVolumeEntry 27 }

xsanVolumeControllerIndex OBJECT-TYPE
    SYNTAX  INTEGER
    MAX-ACCESS  read-only
    STATUS  current
    DESCRIPTION
    "The MDC Index of the metadata controller"
::= { xsanVolumeEntry 28 }

-- Xsan Storage Pools

-- Lithium Site table
-- This table contains one entry for each site
-- configured under a particular

xsanStripeGroupTable OBJECT-TYPE
    SYNTAX      SEQUENCE OF XsanStripeGroupEntry
    MAX-ACCESS  not-accessible
    STATUS      current
    DESCRIPTION
    "The table of stripe groups indexed by xsanVolume"
::= { xsan 2 }

xsanStripeGroupEntry OBJECT-TYPE
    SYNTAX      XsanStripeGroupEntry
    MAX-ACCESS  not-accessible
    STATUS      current
    DESCRIPTION
     "An Xsan Stripe Group (Storage Pool)"
    INDEX { xsanVolumeIndex, xsanStripeGroupIndex }
::= { xsanStripeGroupTable 1 }

XsanStripeGroupEntry ::= SEQUENCE
{
    xsanStringGroupVolumeIndex         Integer32,
    xsanStripeGroupIndex    Integer32,
    xsanStripeGroupName     DisplayString,
    xsanStripeGroupStatus              INTEGER,
    xsanStripeGroupTotalBlocks  Counter64,
    xsanStripeGroupReservedBlocks   Counter64,
    xsanStripeGroupFreeBlocks   Counter64,
    xsanStripeGroupTotalKBlocks Gauge32,
    xsanStripeGroupReservedKBlocks  Gauge32,
    xsanStripeGroupFreeKBlocks  Gauge32,
    xsanStripeGroupUtilization Gauge32,
    xsanStripeGroupMultiPathMethod  DisplayString,
    xsanStripeGroupStripeDepth  Integer32,
    xsanStripeGroupStripeBreadth    Integer32,
    xsanStripeGroupAffinityKey  DisplayString,
    xsanStripeGroupRTLimitIOPerSecond   Gauge32,
    xsanStripeGroupNonRTReserveIOPerSecond  Gauge32,
    xsanStripeGroupRTCommittedIOPerSecond   Gauge32,
    xsanStripeGroupNonRTClients Gauge32,
    xsanStripeGroupNonRTHostIOPerSecond Gauge32,
    xsanStripeGroupTotalMBytes Gauge32,
    xsanStripeGroupFreeMBytes Gauge32,
    xsanStripeGroupUsedMBytes Gauge32
}

xsanStringGroupVolumeIndex OBJECT-TYPE
    SYNTAX      Integer32 (1..65535)
    MAX-ACCESS  not-accessible
    STATUS      current
    DESCRIPTION
    "The index of the xsanVolume to which this stripe group belongs"
::= { xsanStripeGroupEntry 1 }

xsanStripeGroupIndex OBJECT-TYPE
    SYNTAX      Integer32 (1..65535)
    MAX-ACCESS  not-accessible
    STATUS      current
    DESCRIPTION
    "The index of the Stripe Group"
::= { xsanStripeGroupEntry 2 }

xsanStripeGroupName OBJECT-TYPE
    SYNTAX DisplayString
    MAX-ACCESS read-only
    STATUS current
    DESCRIPTION
    "The name of the Stripe Group as reported in 'show long'"
::= { xsanStripeGroupEntry 3 }

xsanStripeGroupStatus OBJECT-TYPE
    SYNTAX INTEGER {
        unknown (0),
        up (1)
    }
    MAX-ACCESS read-only
    STATUS current
    DESCRIPTION
    "The state of the Stripe Group as reported in 'show long'"
::= { xsanStripeGroupEntry 4 }

xsanStripeGroupTotalBlocks OBJECT-TYPE
    SYNTAX Counter64
    MAX-ACCESS read-only
    STATUS current
    DESCRIPTION
    "The number of blocks in the Stripe Group as reported in 'show long'"
::= { xsanStripeGroupEntry 5 }

xsanStripeGroupReservedBlocks OBJECT-TYPE
    SYNTAX Counter64
    MAX-ACCESS read-only
    STATUS current
    DESCRIPTION
    "The number of reserved blocks in the Stripe Group as reported in 'show long'"
::= { xsanStripeGroupEntry 6 }

xsanStripeGroupFreeBlocks OBJECT-TYPE
    SYNTAX Counter64
    MAX-ACCESS read-only
    STATUS current
    DESCRIPTION
    "The number of free blocks in the Stripe Group as reported in 'show long'"
::= { xsanStripeGroupEntry 7 }

xsanStripeGroupTotalKBlocks OBJECT-TYPE
    SYNTAX Gauge32
    MAX-ACCESS read-only
    STATUS current
    DESCRIPTION
    "The number of blocks in the Stripe Group as reported in 'show long' divided by 1000 (KiloBlocks)"
::= { xsanStripeGroupEntry 8 }

xsanStripeGroupReservedKBlocks OBJECT-TYPE
    SYNTAX Gauge32
    MAX-ACCESS read-only
    STATUS current
    DESCRIPTION
    "The number of reserved blocks in the Stripe Group as reported in 'show long' divided by 1000 (KiloBlocks)"
::= { xsanStripeGroupEntry 9 }

xsanStripeGroupFreeKBlocks OBJECT-TYPE
    SYNTAX Gauge32
    MAX-ACCESS read-only
    STATUS current
    DESCRIPTION
    "The number of free blocks in the Stripe Group as reported in 'show long' divided by 1000 (KiloBlocks)"
::= { xsanStripeGroupEntry 10 }

xsanStripeGroupUtilization OBJECT-TYPE
    SYNTAX Gauge32
    UNITS "%"
    MAX-ACCESS read-only
    STATUS current
    DESCRIPTION
    "The Utilization of the Stripe Group as reported in 'show long' (reserved blocks over total blocks)"
::= { xsanStripeGroupEntry 11 }

xsanStripeGroupMultiPathMethod OBJECT-TYPE
    SYNTAX DisplayString
    MAX-ACCESS read-only
    STATUS current
    DESCRIPTION
    "The MultipPath Method of the Stripe Group as reported in 'show long'"
::= { xsanStripeGroupEntry 12 }

xsanStripeGroupStripeDepth OBJECT-TYPE
    SYNTAX Integer32
    MAX-ACCESS read-only
    STATUS current
    DESCRIPTION
    "The stripe depth of the Stripe Group as reported in 'show long'"
::= { xsanStripeGroupEntry 13 }

xsanStripeGroupStripeBreadth OBJECT-TYPE
    SYNTAX Integer32
    MAX-ACCESS read-only
    STATUS current
    DESCRIPTION
    "The stripe breadth (in blocks) of the Stripe Group as reported in 'show long'"
::= { xsanStripeGroupEntry 14 }

xsanStripeGroupAffinityKey OBJECT-TYPE
    SYNTAX DisplayString
    MAX-ACCESS read-only
    STATUS current
    DESCRIPTION
    "The affinity of the Stripe Group as reported in 'show long'"
::= { xsanStripeGroupEntry 15 }

xsanStripeGroupRTLimitIOPerSecond OBJECT-TYPE
    SYNTAX Gauge32
    MAX-ACCESS read-only
    STATUS current
    DESCRIPTION
    "The 'Realtime limit IO/sec' of the Stripe Group as reported in 'show long'"
::= { xsanStripeGroupEntry 16 }

xsanStripeGroupNonRTReserveIOPerSecond OBJECT-TYPE
    SYNTAX Gauge32
    MAX-ACCESS read-only
    STATUS current
    DESCRIPTION
    "The 'Non-Realtime reserve IO/sec' of the Stripe Group as reported in 'show long'"
::= { xsanStripeGroupEntry 17 }

xsanStripeGroupRTCommittedIOPerSecond OBJECT-TYPE
    SYNTAX Gauge32
    MAX-ACCESS read-only
    STATUS current
    DESCRIPTION
    "The 'Committed RTIO/sec' of the Stripe Group as reported in 'show long'"
::= { xsanStripeGroupEntry 18 }

xsanStripeGroupNonRTClients OBJECT-TYPE
    SYNTAX Gauge32
    MAX-ACCESS read-only
    STATUS current
    DESCRIPTION
    "The 'Non-RTIO clients' of the Stripe Group as reported in 'show long'"
::= { xsanStripeGroupEntry 19 }

xsanStripeGroupNonRTHostIOPerSecond OBJECT-TYPE
    SYNTAX Gauge32
    MAX-ACCESS read-only
    STATUS current
    DESCRIPTION
    "The 'Non-RTIO hint IO/sec' of the Stripe Group as reported in 'show long'"
::= { xsanStripeGroupEntry 20 }

xsanStripeGroupTotalMBytes OBJECT-TYPE
    SYNTAX  Gauge32
    UNITS   "MBytes"
    MAX-ACCESS  read-only
    STATUS  current
    DESCRIPTION
    "Total number of bytes in the Stripe Group divided by 1024 * 1024 (Megabytes)"
::= { xsanStripeGroupEntry 21 }

xsanStripeGroupFreeMBytes OBJECT-TYPE
    SYNTAX  Gauge32
    UNITS   "MBytes"
    MAX-ACCESS  read-only
    STATUS  current
    DESCRIPTION
    "The number of free bytes in the Stripe Group divided by 1024 * 1024 (Megabytes)"
::= { xsanStripeGroupEntry 22 }

xsanStripeGroupUsedMBytes OBJECT-TYPE
    SYNTAX  Gauge32
    UNITS   "MBytes"
    MAX-ACCESS  read-only
    STATUS  current
    DESCRIPTION
    "The number of used bytes in the Stripe Group divided by 1024 * 1024 (Megabytes)"
::= { xsanStripeGroupEntry 23 }


-- Xsan Nodes (LUNs in Stripe Groups)

xsanNodeTable OBJECT-TYPE
    SYNTAX      SEQUENCE OF XsanNodeEntry
    MAX-ACCESS  not-accessible
    STATUS      current
    DESCRIPTION
    "The table of LUNs in a Stripe Group indexed by xsanVolumeIndex.xsanStripeGroupIndex.xsanNodeIndex"
::= { xsan 3 }

xsanNodeEntry OBJECT-TYPE
    SYNTAX      XsanNodeEntry
    MAX-ACCESS  not-accessible
    STATUS      current
    DESCRIPTION
     "An Xsan Node (LUN in a Stripe Group)"
    INDEX { xsanVolumeIndex, xsanStripeGroupIndex, xsanNodeIndex }
::= { xsanNodeTable 1 }

XsanNodeEntry ::= SEQUENCE
{
    xsanNodeVolumeIndex             Integer32,
    xsanNodeStripeGroupIndex        Integer32,
    xsanNodeIndex               Integer32,
    xsanNodeName                DisplayString,
    xsanNodeController          DisplayString,
    xsanNodeSerial              DisplayString,
    xsanNodeGUID                DisplayString,
    xsanNodeDevice              DisplayString,
    xsanNodeDeviceLabel         DisplayString,
    xsanNodeFSType              DisplayString,
    xsanNodeSectorSize          Gauge32,
    xsanNodeSectors             Counter64,
    xsanNodeMaxSectors          Counter64,
    xsanNodeKSectors            Gauge32,
    xsanNodeMaxKSectors         Gauge32,
    xsanNodeVisible             INTEGER,
    xsanNodeSize                Gauge32
}

xsanNodeVolumeIndex OBJECT-TYPE
    SYNTAX      Integer32 (1..65535)
    MAX-ACCESS  not-accessible
    STATUS      current
    DESCRIPTION
    "The index of the xsanVolume to which this stripe group belongs"
::= { xsanNodeEntry 1 }

xsanNodeStripeGroupIndex OBJECT-TYPE
    SYNTAX      Integer32 (1..65535)
    MAX-ACCESS  not-accessible
    STATUS      current
    DESCRIPTION
    "The index of the Stripe Group that this Node belongs to"
::= { xsanNodeEntry 2 }

xsanNodeIndex OBJECT-TYPE
    SYNTAX      Integer32 (1..65535)
    MAX-ACCESS  not-accessible
    STATUS      current
    DESCRIPTION
    "The index of the Node (LUN)"
::= { xsanNodeEntry 3 }

xsanNodeName OBJECT-TYPE
    SYNTAX DisplayString
    MAX-ACCESS read-only
    STATUS current
    DESCRIPTION
    "The name of the LUN as reported in 'show long'"
::= { xsanNodeEntry 4 }

xsanNodeController OBJECT-TYPE
    SYNTAX DisplayString
    MAX-ACCESS read-only
    STATUS current
    DESCRIPTION
    "The Controller of the Node as reported by cvlabel"
::= { xsanNodeEntry 5 }

xsanNodeSerial OBJECT-TYPE
    SYNTAX DisplayString
    MAX-ACCESS read-only
    STATUS current
    DESCRIPTION
    "The Serial of the Node (WWN for FibreChannel) as reported by cvlabel"
::= { xsanNodeEntry 6 }

xsanNodeGUID OBJECT-TYPE
    SYNTAX DisplayString
    MAX-ACCESS read-only
    STATUS current
    DESCRIPTION
    "The GUID of the Node as reported by cvlabel"
::= { xsanNodeEntry 7 }

xsanNodeDevice OBJECT-TYPE
    SYNTAX DisplayString
    MAX-ACCESS read-only
    STATUS current
    DESCRIPTION
    "The Disk Device of the Node (e.g. /dev/rdisk0) as reported by cvlabel"
::= { xsanNodeEntry 8 }

xsanNodeDeviceLabel OBJECT-TYPE
    SYNTAX DisplayString
    MAX-ACCESS read-only
    STATUS current
    DESCRIPTION
    "The Disk Device Label of the Node as reported by cvlabel"
::= { xsanNodeEntry 9 }

xsanNodeFSType OBJECT-TYPE
    SYNTAX DisplayString
    MAX-ACCESS read-only
    STATUS current
    DESCRIPTION
    "The File System used by the Node as reported by cvlabel"
::= { xsanNodeEntry 10 }

xsanNodeSectorSize OBJECT-TYPE
    SYNTAX  Gauge32
    UNITS   "Bytes"
    MAX-ACCESS  read-only
    STATUS  current
    DESCRIPTION
    "The number of bytes per sector on the Node as reported by cvlabel"
::= { xsanNodeEntry 11 }

xsanNodeSectors OBJECT-TYPE
    SYNTAX  Counter64
    UNITS   "Sectors"
    MAX-ACCESS  read-only
    STATUS  current
    DESCRIPTION
    "The number of sectors on the Node as reported by cvlabel"
::= { xsanNodeEntry 12 }

xsanNodeMaxSectors OBJECT-TYPE
    SYNTAX  Counter64
    UNITS   "Sectors"
    MAX-ACCESS  read-only
    STATUS  current
    DESCRIPTION
    "The maximum number of sectors on the Node as reported by cvlabel"
::= { xsanNodeEntry 13 }

xsanNodeKSectors OBJECT-TYPE
    SYNTAX  Gauge32
    UNITS   "KSectors"
    MAX-ACCESS  read-only
    STATUS  current
    DESCRIPTION
    "The number of sectors on the Node as reported by cvlabel divided by 1000 (KSectors)"
::= { xsanNodeEntry 14 }

xsanNodeMaxKSectors OBJECT-TYPE
    SYNTAX  Gauge32
    UNITS   "KSectors"
    MAX-ACCESS  read-only
    STATUS  current
    DESCRIPTION
    "The maximum number of sectors on the Node as reported by cvlabel divided by 1000 (KSectors)"
::= { xsanNodeEntry 15 }

xsanNodeVisible OBJECT-TYPE
    SYNTAX  INTEGER {
        yes (1),
        no (0)
    }
    MAX-ACCESS  read-only
    STATUS  current
    DESCRIPTION
    "Indicates whether the Node is shown in the output from cvlabel"
::= { xsanNodeEntry 16 }

xsanNodeSize OBJECT-TYPE
    SYNTAX  Gauge32
    UNITS   "MBytes"
    MAX-ACCESS  read-only
    STATUS  current
    DESCRIPTION
    "The size of the the Node calculated from the sectors and sector size in Megabytes"
::= { xsanNodeEntry 17 }


-- Xsan Affinities

xsanAffinityTable OBJECT-TYPE
    SYNTAX SEQUENCE OF XsanAffinityEntry
    MAX-ACCESS not-accessible
    STATUS  current
    DESCRIPTION
    "Affinitys groups as reported in 'show long' with utilisation calculated by Xsnmp"
::= { xsan 4 }

xsanAffinityEntry OBJECT-TYPE
    SYNTAX     XsanAffinityEntry
    MAX-ACCESS not-accessible
    STATUS     current
    DESCRIPTION
        "An entry per Affinity as reported in the AffinityKey in 'show long' indexed by xsanVolumeIndex.xsanAffinityIndex"
    INDEX      { xsanVolumeIndex, xsanAffinityIndex }
::= { xsanAffinityTable 1 }

XsanAffinityEntry ::= SEQUENCE {
    xsanAffinityVolumeIndex         Integer32,
    xsanAffinityIndex               Integer32,
    xsanAffinityName                DisplayString,
    xsanAffinityStripeGroups        Gauge32,
    xsanAffinityTotalKBlocks        Gauge32,
    xsanAffinityFreeKBlocks         Gauge32,
    xsanAffinityTotalBlocks         Counter64,
    xsanAffinityFreeBlocks          Counter64,
    xsanAffinityUtilization         Gauge32,
    xsanAffinityTotalMBytes         Gauge32,
    xsanAffinityFreeMBytes     Gauge32,
    xsanAffinityUsedMBytes     Gauge32
}

xsanAffinityVolumeIndex OBJECT-TYPE
    SYNTAX  Integer32 (1..65535)
    MAX-ACCESS  not-accessible
    STATUS  current
    DESCRIPTION
    "Volume index that the affinity belongs to."
::= { xsanAffinityEntry 1 }

xsanAffinityIndex OBJECT-TYPE
    SYNTAX  Integer32 (1..65535)
    MAX-ACCESS  not-accessible
    STATUS  current
    DESCRIPTION
    "Volume index assigned by Xsnmp."
::= { xsanAffinityEntry 2 }

xsanAffinityName OBJECT-TYPE
    SYNTAX  DisplayString
    MAX-ACCESS  read-only
    STATUS  current
    DESCRIPTION
    "The name of the FSS as reported in fsmlist"
::= { xsanAffinityEntry 3 }

xsanAffinityStripeGroups OBJECT-TYPE
    SYNTAX  Gauge32
    MAX-ACCESS  read-only
    STATUS  current
    DESCRIPTION
    "The number of stripe groups in the Affinity Group"
::= { xsanAffinityEntry 4 }

xsanAffinityTotalKBlocks OBJECT-TYPE
    SYNTAX  Gauge32
    UNITS   "KBlocks"
    MAX-ACCESS  read-only
    STATUS  current
    DESCRIPTION
    "Total number of blocks divided by 1,000 (KiloBlocks) calculated as a sum of all Stripe Groups in the Affinity"
::= { xsanAffinityEntry 5 }

xsanAffinityFreeKBlocks OBJECT-TYPE
    SYNTAX  Gauge32
    UNITS   "KBlocks"
    MAX-ACCESS  read-only
    STATUS  current
    DESCRIPTION
    "Number of free blocks divided by 1,000 (KiloBlocks) calculated as a sum of all Stripe Groups in the Affinity"
::= { xsanAffinityEntry 6 }

xsanAffinityTotalBlocks OBJECT-TYPE
    SYNTAX  Counter64
    UNITS   "Blocks"
    MAX-ACCESS  read-only
    STATUS  current
    DESCRIPTION
    "Total number of blocks calculated as a sum of all Stripe Groups in the Affinity"
::= { xsanAffinityEntry 7 }

xsanAffinityFreeBlocks OBJECT-TYPE
    SYNTAX  Counter64
    UNITS   "Blocks"
    MAX-ACCESS  read-only
    STATUS  current
    DESCRIPTION
    "Number of free blocks calculated as a sum of all Stripe Groups in the Affinity"
::= { xsanAffinityEntry 8 }

xsanAffinityUtilization OBJECT-TYPE
    SYNTAX  Gauge32
    UNITS   "%"
    MAX-ACCESS  read-only
    STATUS  current
    DESCRIPTION
    "The Utilization of the drive expressed as free space over total size calculated as an average of all Stripe Groups in the Affinity"
::= { xsanAffinityEntry 9 }

xsanAffinityTotalMBytes OBJECT-TYPE
    SYNTAX  Gauge32
    UNITS   "MBytes"
    MAX-ACCESS  read-only
    STATUS  current
    DESCRIPTION
    "Total number of bytes in the Affinity divided by 1024 * 1024 (Megabytes)"
::= { xsanAffinityEntry 10 }

xsanAffinityFreeMBytes OBJECT-TYPE
    SYNTAX  Gauge32
    UNITS   "MBytes"
    MAX-ACCESS  read-only
    STATUS  current
    DESCRIPTION
    "The number of free bytes in the Affinity divided by 1024 * 1024 (Megabytes)"
::= { xsanAffinityEntry 11 }

xsanAffinityUsedMBytes OBJECT-TYPE
    SYNTAX  Gauge32
    UNITS   "MBytes"
    MAX-ACCESS  read-only
    STATUS  current
    DESCRIPTION
    "The number of used bytes in the Affinity divided by 1024 * 1024 (Megabytes)"
::= { xsanAffinityEntry 12 }


-- Xsan Visible Disks
    
-- Xsan Computers 

--
-- Xserve Intel Hardware LOM
--

xserve OBJECT IDENTIFIER ::= { xsnmpObjects 2 }

--
-- Host Filesystems
--

fs OBJECT IDENTIFIER ::= { xsnmpObjects 4 }

fsTable OBJECT-TYPE
    SYNTAX SEQUENCE OF FsEntry
    MAX-ACCESS not-accessible
    STATUS  current
    DESCRIPTION
    "Filesystrems reported by df"
::= { fs 1 }

fsEntry OBJECT-TYPE
    SYNTAX     FsEntry
    MAX-ACCESS not-accessible
    STATUS     current
    DESCRIPTION
        "An entry per line in df"
    INDEX      { fsIndex }
::= { fsTable 1 }

FsEntry ::= SEQUENCE {
    fsIndex      Integer32,
    fsFilesystem DisplayString,
    fsMountpoint DisplayString,
    fsSize       Gauge32,
    fsUsed       Gauge32,
    fsAvail      Gauge32,
    fsUtilization   Gauge32,
    fsWriteable INTEGER,
    fsRemovable INTEGER,
    fsBootable INTEGER,
    fsSmartStatus INTEGER,
    fsSmartMessage DisplayString
}

fsIndex OBJECT-TYPE
    SYNTAX  Integer32 (1..65535)
    MAX-ACCESS  not-accessible
    STATUS  current
    DESCRIPTION
    "Row number for the output from df."
::= { fsEntry 1 }

fsFilesystem OBJECT-TYPE
    SYNTAX  DisplayString
    MAX-ACCESS  read-only
    STATUS  current
    DESCRIPTION
    "The filesystem (e.g. /dev/disk0s2)"
::= { fsEntry 2 }

fsMountpoint OBJECT-TYPE
    SYNTAX  DisplayString
    MAX-ACCESS  read-only
    STATUS  current
    DESCRIPTION
    "The mount point (e.g. /Volumes/Data)"
::= { fsEntry 3 }

fsSize OBJECT-TYPE
    SYNTAX  Gauge32
    UNITS   "MBytes"
    MAX-ACCESS  read-only
    STATUS  current
    DESCRIPTION
    "The size of the volume in Megabytes"
::= { fsEntry 4 }

fsUsed OBJECT-TYPE
    SYNTAX  Gauge32
    UNITS   "MBytes"
    MAX-ACCESS  read-only
    STATUS  current
    DESCRIPTION
    "The number of bytes used on the volume in Megabytes"
::= { fsEntry 5 }

fsAvail OBJECT-TYPE
    SYNTAX  Gauge32
    UNITS   "MBytes"
    MAX-ACCESS  read-only
    STATUS  current
    DESCRIPTION
    "The number of bytes available on the volume in Megabytes"
::= { fsEntry 6 }

fsUtilization OBJECT-TYPE
    SYNTAX  Gauge32
    UNITS   "%"
    MAX-ACCESS  read-only
    STATUS  current
    DESCRIPTION
    "The Utilization of the drive expressed as a percentage of space used"
::= { fsEntry 7 }

fsWriteable OBJECT-TYPE
    SYNTAX  INTEGER {
      unknown (-1),
      yes (1),
      no (0)
    }
    MAX-ACCESS  read-only
    STATUS  current
    DESCRIPTION
    "Indicates whether the file system is writeable as indicated by diskutil"
::= { fsEntry 8 }

fsRemovable OBJECT-TYPE
    SYNTAX  INTEGER {
      unknown (-1),
      yes (1),
      no (0)
    }
    MAX-ACCESS  read-only
    STATUS  current
    DESCRIPTION
    "Indicates whether the file system is removable as indicated by diskutil"
::= { fsEntry 9 }

fsBootable OBJECT-TYPE
    SYNTAX  INTEGER {
      unknown (-1),
      yes (1),
      no (0)
    }
    MAX-ACCESS  read-only
    STATUS  current
    DESCRIPTION
    "Indicates whether the file system is bootable as indicated by diskutil"
::= { fsEntry 10 }

fsSmartStatus OBJECT-TYPE
    SYNTAX  INTEGER {
      unknown (-1),
      notSupported (0),
      verified (1),
      warning (2)
    }
    MAX-ACCESS  read-only
    STATUS  current
    DESCRIPTION
    "The SMART status of the disk as reported by diskutil"
::= { fsEntry 11 }

fsSmartMessage OBJECT-TYPE
    SYNTAX  DisplayString
    MAX-ACCESS  read-only
    STATUS  current
    DESCRIPTION
    "The SMART status message for the disk as reported by diskutil"
::= { fsEntry 12 }

--
-- Host RAM
--

ram OBJECT IDENTIFIER ::= { xsnmpObjects 3 }

ramWired OBJECT-TYPE
    SYNTAX  Gauge32
    UNITS   "MBytes"
    MAX-ACCESS read-only
    STATUS current
    DESCRIPTION
        "Wired memory as reported by top in Megabytes"
    ::= { ram 1 }

ramActive OBJECT-TYPE
    SYNTAX  Gauge32
    UNITS   "MBytes"
    MAX-ACCESS read-only
    STATUS current
    DESCRIPTION
        "Active memory as reported by top in Megabytes"
    ::= { ram 2 }

ramInactive OBJECT-TYPE
    SYNTAX  Gauge32
    UNITS   "MBytes"
    MAX-ACCESS read-only
    STATUS current
    DESCRIPTION
        "Inactive memory as reported by top in Megabytes"
    ::= { ram 3 }

ramUsed OBJECT-TYPE
    SYNTAX  Gauge32
    UNITS   "MBytes"
    MAX-ACCESS read-only
    STATUS current
    DESCRIPTION
        "Used memory as reported by top in Megabytes"
    ::= { ram 4 }

ramFree OBJECT-TYPE
    SYNTAX  Gauge32
    UNITS   "MBytes"
    MAX-ACCESS read-only
    STATUS current
    DESCRIPTION
        "Free memory as reported by top in Megabytes"
    ::= { ram 5 }

--
-- Xsnmp Internal
--

xsnmpInternal OBJECT IDENTIFIER ::= { xsnmpObjects 5 }

xsnmpVersion OBJECT-TYPE
    SYNTAX  Gauge32
    MAX-ACCESS read-only
    STATUS current
    DESCRIPTION
        "Version number for Xsnmp"
    ::= { xsnmpInternal 1 }

--
-- RAID (Host RAID Card)
--

raid OBJECT IDENTIFIER ::= { xsnmpObjects 6 }

-- RAID Info

raidInfo OBJECT IDENTIFIER ::= { raid 1 }

raidGeneralStatus OBJECT-TYPE
    SYNTAX  INTEGER {
        good (1), 
        issuesFound (2),
        unknown (0)
    }
    MAX-ACCESS read-only
    STATUS current
    DESCRIPTION
        "The General Status of the RAID card"
    ::= { raidInfo 1 }

raidGeneralStatusMessage OBJECT-TYPE
    SYNTAX  DisplayString
    MAX-ACCESS read-only
    STATUS current
    DESCRIPTION
        "The General Status of the RAID card direct from raidutil"
    ::= { raidInfo 2 }

raidBatteryStatus OBJECT-TYPE
    SYNTAX  INTEGER {
        charged (1), 
        conditioning (2),
        chargingInsufficientCharge (3),
        notChargingInsufficientCharge (4),
        failed (5),
        precharging (6),
        unknown (0)
    }
    MAX-ACCESS read-only
    STATUS current
    DESCRIPTION
        "The Battery Status of the RAID card"
    ::= { raidInfo 3 }

raidBatteryStatusMessage OBJECT-TYPE
    SYNTAX  DisplayString
    MAX-ACCESS read-only
    STATUS current
    DESCRIPTION
        "The Battery Status message for the RAID card from raidutil"
    ::= { raidInfo 4 }

raidHardwareVersion OBJECT-TYPE
    SYNTAX  DisplayString
    MAX-ACCESS read-only
    STATUS current
    DESCRIPTION
        "The hardware version of the RAID card"
    ::= { raidInfo 5 }

raidFirmwareVersion OBJECT-TYPE
    SYNTAX  DisplayString
    MAX-ACCESS read-only
    STATUS current
    DESCRIPTION
        "The firmware version of the RAID card"
    ::= { raidInfo 6 }

raidWriteCache OBJECT-TYPE
    SYNTAX  INTEGER {
        enabled (1), 
        disabled (2),
        unknown (0)
    }
    MAX-ACCESS read-only
    STATUS current
    DESCRIPTION
        "The Write Cache status of the RAID card"
    ::= { raidInfo 7 }

-- RAID Sets

raidSetTable OBJECT-TYPE
    SYNTAX SEQUENCE OF RaidSetEntry
    MAX-ACCESS not-accessible
    STATUS  current
    DESCRIPTION
    "RAID sets reported by raidutil"
::= { raid 2 }

raidSetEntry OBJECT-TYPE
    SYNTAX     RaidSetEntry
    MAX-ACCESS not-accessible
    STATUS     current
    DESCRIPTION
        "An entry per RAID Set in raidutil"
    INDEX      { raidSetIndex }
::= { raidSetTable 1 }

RaidSetEntry ::= SEQUENCE {
    raidSetIndex    Integer32,
    raidSetName     DisplayString,
    raidSetType     DisplayString,
    raidSetSize     Gauge32,
    raidSetUnused   Gauge32,
    raidSetComments DisplayString
}

raidSetIndex OBJECT-TYPE
    SYNTAX  Integer32 (1..65535)
    MAX-ACCESS  not-accessible
    STATUS  current
    DESCRIPTION
    "Row number for the output from raidutil."
::= { raidSetEntry 1 }

raidSetName OBJECT-TYPE
    SYNTAX  DisplayString
    MAX-ACCESS  read-only
    STATUS  current
    DESCRIPTION
    "The name of the RAID Set"
::= { raidSetEntry 2 }

raidSetType OBJECT-TYPE
    SYNTAX  DisplayString
    MAX-ACCESS  read-only
    STATUS  current
    DESCRIPTION
    "The type of the RAID set (e.g. RAID5, RAID0, etc)"
::= { raidSetEntry 3 }

raidSetSize OBJECT-TYPE
    SYNTAX  Gauge32
    UNITS   "MBytes"
    MAX-ACCESS  read-only
    STATUS  current
    DESCRIPTION
    "The total size of the RAID Set in Megabytes"
::= { raidSetEntry 4 }

raidSetUnused OBJECT-TYPE
    SYNTAX  Gauge32
    UNITS   "MBytes"
    MAX-ACCESS  read-only
    STATUS  current
    DESCRIPTION
    "The amount of unallocated capacity in Megabytes"
::= { raidSetEntry 5 }

raidSetComments OBJECT-TYPE
    SYNTAX  DisplayString
    MAX-ACCESS  read-only
    STATUS  current
    DESCRIPTION
    "RAID Set comments directly from raidutil"
::= { raidSetEntry 6 }

-- RAID Drives

raidDriveTable OBJECT-TYPE
    SYNTAX SEQUENCE OF RaidDriveEntry
    MAX-ACCESS not-accessible
    STATUS  current
    DESCRIPTION
    "RAID drives reported by raidutil"
::= { raid 3 }

raidDriveEntry OBJECT-TYPE
    SYNTAX     RaidDriveEntry
    MAX-ACCESS not-accessible
    STATUS     current
    DESCRIPTION
        "An entry per RAID Drive in raidutil"
    INDEX      { raidDriveIndex }
::= { raidDriveTable 1 }

RaidDriveEntry ::= SEQUENCE {
    raidDriveIndex         Integer32,
    raidDriveLocation      DisplayString,
    raidDriveSetName       DisplayString,
    raidDriveSize          Gauge32,
    raidDriveStatus        INTEGER,
    raidDriveStatusMessage DisplayString,
    raidDriveSetIndex      Integer32
}

raidDriveIndex OBJECT-TYPE
    SYNTAX  Integer32 (1..65535)
    MAX-ACCESS  not-accessible
    STATUS  current
    DESCRIPTION
    "Row number for the output from raidutil."
::= { raidDriveEntry 1 }

raidDriveLocation OBJECT-TYPE
    SYNTAX  DisplayString
    MAX-ACCESS  read-only
    STATUS  current
    DESCRIPTION
    "The location or name of the drive"
::= { raidDriveEntry 2 }

raidDriveSetName OBJECT-TYPE
    SYNTAX  DisplayString
    MAX-ACCESS  read-only
    STATUS  current
    DESCRIPTION
    "The name of the RAID Set that this drive belongs to"
::= { raidDriveEntry 3 }

raidDriveSize OBJECT-TYPE
    SYNTAX  Gauge32
    UNITS   "MBytes"
    MAX-ACCESS  read-only
    STATUS  current
    DESCRIPTION
    "The total size of the drive in Megabytes"
::= { raidDriveEntry 4 }

raidDriveStatus OBJECT-TYPE
    SYNTAX  INTEGER {
        reliable (1), 
        failurePredicted (2),
        failed (3),
        missing (4),
        incompatMetaData (5),
        spare (6),
        notAssigned (7),
        unknown (0)
    }
    MAX-ACCESS read-only
    STATUS current
    DESCRIPTION
        "The status of the drive"
::= { raidDriveEntry 5 }

raidDriveStatusMessage OBJECT-TYPE
    SYNTAX  DisplayString
    MAX-ACCESS read-only
    STATUS current
    DESCRIPTION
        "The drive status message from raidutil"
::= { raidDriveEntry 6 }

raidDriveSetIndex OBJECT-TYPE
    SYNTAX  Integer32 (1..65535)
    MAX-ACCESS  read-only
    STATUS  current
    DESCRIPTION
    "Row number of the RAID Set that this drive belongs to."
::= { raidDriveEntry 7 }

-- RAID Volumes

raidVolumeTable OBJECT-TYPE
    SYNTAX SEQUENCE OF RaidVolumeEntry
    MAX-ACCESS not-accessible
    STATUS  current
    DESCRIPTION
    "RAID volumes reported by raidutil"
::= { raid 4 }

raidVolumeEntry OBJECT-TYPE
    SYNTAX     RaidVolumeEntry
    MAX-ACCESS not-accessible
    STATUS     current
    DESCRIPTION
        "An entry per RAID Volume in raidutil"
    INDEX      { raidVolumeIndex }
::= { raidVolumeTable 1 }

RaidVolumeEntry ::= SEQUENCE {
    raidVolumeIndex         Integer32,
    raidVolumeName          DisplayString,
    raidVolumeSetName       DisplayString,
    raidVolumeType          DisplayString,
    raidVolumeSize          Gauge32,
    raidVolumeStatus        INTEGER,
    raidVolumeStatusMessage DisplayString,
    raidVolumeComments      DisplayString,
    raidVolumeSetIndex      Integer32
}

raidVolumeIndex OBJECT-TYPE
    SYNTAX  Integer32 (1..65535)
    MAX-ACCESS  not-accessible
    STATUS  current
    DESCRIPTION
    "Row number for the output from raidutil."
::= { raidVolumeEntry 1 }

raidVolumeName OBJECT-TYPE
    SYNTAX  DisplayString
    MAX-ACCESS  read-only
    STATUS  current
    DESCRIPTION
    "The name of the volume"
::= { raidVolumeEntry 2 }

raidVolumeSetName OBJECT-TYPE
    SYNTAX  DisplayString
    MAX-ACCESS  read-only
    STATUS  current
    DESCRIPTION
    "The name of the RAID Set that this volume belongs to"
::= { raidVolumeEntry 3 }

raidVolumeType OBJECT-TYPE
    SYNTAX  DisplayString
    MAX-ACCESS  read-only
    STATUS  current
    DESCRIPTION
    "The RAID type of the volume"
::= { raidVolumeEntry 4 }

raidVolumeSize OBJECT-TYPE
    SYNTAX  Gauge32
    UNITS   "MBytes"
    MAX-ACCESS  read-only
    STATUS  current
    DESCRIPTION
    "The total size of the volume in Megabytes"
::= { raidVolumeEntry 5 }

raidVolumeStatus OBJECT-TYPE
    SYNTAX  INTEGER {
        viable (1), 
        notViable (2),
        notInitialized (3),
        degraded (4),
        unknown (0)
    }
    MAX-ACCESS read-only
    STATUS current
    DESCRIPTION
        "The status of the volume"
::= { raidVolumeEntry 6 }

raidVolumeStatusMessage OBJECT-TYPE
    SYNTAX  DisplayString
    MAX-ACCESS read-only
    STATUS current
    DESCRIPTION
        "The volume status message from raidutil"
::= { raidVolumeEntry 7 }

raidVolumeComments OBJECT-TYPE
    SYNTAX  DisplayString
    MAX-ACCESS  read-only
    STATUS  current
    DESCRIPTION
    "The volume comments directly from raidutil"
::= { raidVolumeEntry 8 }

raidVolumeSetIndex OBJECT-TYPE
    SYNTAX  Integer32 (1..65535)
    MAX-ACCESS  read-only
    STATUS  current
    DESCRIPTION
    "Row number of the RAID Set that this volume belongs to."
::= { raidVolumeEntry 9 }

--
-- Time Machine Backup
--

timeMachine OBJECT IDENTIFIER ::= { xsnmpObjects 7 }

tmDaysSinceBackup OBJECT-TYPE
    SYNTAX  Integer
    UNITS   "Days"
    MAX-ACCESS read-only
    STATUS current
    DESCRIPTION
        "Number of days since last successful backup"
    ::= { timeMachine 1 }

tmBlockSize OBJECT-TYPE
    SYNTAX  Integer
    UNITS   "Bytes"
    MAX-ACCESS read-only
    STATUS current
    DESCRIPTION
        "TimeMachine Backup Block Size as reported by results file in Bytes"
    ::= { timeMachine 2 }

tmBlocksAvailable OBJECT-TYPE
    SYNTAX  Gauge32
    UNITS   "Blocks"
    MAX-ACCESS read-only
    STATUS current
    DESCRIPTION
        "TimeMachine Backup Available Blocks as reported by results file"
    ::= { timeMachine 3 }

tmBlocksToCopy OBJECT-TYPE
    SYNTAX  Gauge32
    UNITS   "Blocks"
    MAX-ACCESS read-only
    STATUS current
    DESCRIPTION
        "TimeMachine Backup Blocks To Copy as reported by results file"
    ::= { timeMachine 4 }

tmBytesAvailable OBJECT-TYPE
    SYNTAX  Gauge32
    UNITS   "MBytes"
    MAX-ACCESS read-only
    STATUS current
    DESCRIPTION
        "TimeMachine Backup Available Bytes as reported by results file in MegaBytes"
    ::= { timeMachine 5 }

tmBytesToCopy OBJECT-TYPE
    SYNTAX  Gauge32
    UNITS   "MBytes"
    MAX-ACCESS read-only
    STATUS current
    DESCRIPTION
        "TimeMachine Backup Bytes To Copy as reported by results file in MegaBytes"
    ::= { timeMachine 6 }
    
tmClientID OBJECT-TYPE
    SYNTAX  DisplayString
    MAX-ACCESS read-only
    STATUS current
    DESCRIPTION
        "TimeMachine Backup ClientID as reported by results file"
    ::= { timeMachine 7 }

tmPaddedBytesRequired OBJECT-TYPE
    SYNTAX  Gauge32
    UNITS   "MBytes"
    MAX-ACCESS read-only
    STATUS current
    DESCRIPTION
        "TimeMachine Backup ClientID as reported by results file"
    ::= { timeMachine 8 }

tmPercentComplete OBJECT-TYPE
    SYNTAX  Integer
    UNITS   "Percent"
    MAX-ACCESS read-only
    STATUS current
    DESCRIPTION
        "TimeMachine Backup Percent Complete"
    ::= { timeMachine 9}
    
tmResult OBJECT-TYPE
    SYNTAX  Integer
    MAX-ACCESS read-only
    STATUS current
    DESCRIPTION
        "TimeMachine Backup Result"
    ::= { timeMachine 10}
    
tmRunning OBJECT-TYPE
    SYNTAX  Integer
    MAX-ACCESS read-only
    STATUS current
    DESCRIPTION
        "TimeMachine Backup Running Status"
    ::= { timeMachine 11}
    
tmOldestSnaphot OBJECT-TYPE
    SYNTAX  Integer
    UNITS   "Days"
    MAX-ACCESS read-only
    STATUS current
    DESCRIPTION
        "TimeMachine Backup Days since oldest complete snapshot"
    ::= { timeMachine 12}
END
